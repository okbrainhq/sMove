# Regenerate current screwless presentation using a SEPARATE pinned GUI process.
# Close this document before running; no automatic save/overwrite of interactive edits.
from pathlib import Path
import subprocess
import FreeCAD as App
root=Path(__file__).resolve().parents[1]
assert not any(Path(d.FileName).name=='smove-r2-enclosure.FCStd' for d in App.listDocuments().values()), 'Close the enclosure document before regenerating presentation; preserve your edits first.'
subprocess.run(['/usr/bin/python3',str(root/'scripts/freecad/run.py'),'housing/render.py'],cwd=root,check=True,timeout=120)
App.openDocument(str(root/'housing/smove-r2-enclosure.FCStd'))
